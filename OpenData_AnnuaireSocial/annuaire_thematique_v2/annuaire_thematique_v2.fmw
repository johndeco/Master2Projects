FME workspace annuaire_thematique_v2.fmw

Parameters:
- ANNUAIRE_MYSQL_CONNECTION =
- CKAN_CONNECTION =
- CKAN_CONNECTION_SAFE.CKAN.CKANDATASTORE =
- DATASET =
- NOM_PRODUCTEUR =
- NUMERO_SIRET =
- PREFIXE_NOM_FICHIER_SORTIE =
- REPERTOIRE_LOCAL_DEPOT =

Writers:
- SAFE.CKAN.CKANDATASTORE_1: SAFE.CKAN.CKANDATASTORE

Note: annuaire_thematique / @auteur: John Marc Dechaud / @description: Traitement FME permettant de générer les données des thèmes de l'annuaire social. / @Date: 25/05/2023 / @version: 1.1 / @status: Production / @param REPERTOIRE_LOCAL_DEPOT --> Repertoire local de dépot / @param PREFIXE_NOM_FICHIER_SORTIE --> Prefix ou nom du fichier de sortie / @param ANNUAIRE_MYSQL_CONNECTION --> Nom de la connexion mysql à utiliser / @param NOM_PRODUCTUER --> Nom du producteur de la donnée dans notre cas c'est le département D'Ille-et-vilaine / @param NUMERO_SIRET --> Numero de siret du département / @param CKAN_CONNECTION --> Nom de la connection au serveur CKAN / @param DATASET -->Nom du jeu de données pour éeposer le fichier / @changelog / 25/05/2023 v1.0 JMD --> Création du traitement
SQLCreator_2
    DATASET = $(ANNUAIRE_MYSQL_CONNECTION)
    EXPOSED_ATTRIBUTE_LIST = THEM_ID THEM_NOM THEM_LEVEL THEM_ID1 THEM_NOM1 THEM_ID2 THEM_NOM2 THEM_ID3 THEM_NOM3 THEM_ID4 THEM_NOM4 PROF_NOM ORG_DATECREA ORG_DATEMAJ
    FORMAT = MYSQL
    MYSQL_NAMED_CONNECTION = $(ANNUAIRE_MYSQL_CONNECTION)
    SQL_STATEMENT:
      SELECT th.THEM_ID, th.THEM_NOM, th.THEM_LEVEL, th1.THEM_ID AS THEM_ID1, th1.THEM_NOM AS THEM_NOM1, th2.THEM_ID AS THEM_ID2, th2.THEM_NOM AS THEM_NOM2, th3.THEM_ID AS THEM_ID3, th3.THEM_NOM AS THEM_NOM3, th4.THEM_ID AS THEM_ID4, th4.THEM_NOM AS THEM_NOM4, pr.PROF_NOM, org.ORG_DATECREA, org.ORG_DATEMAJ
      FROM thematique th
      LEFT JOIN profil_thematique pt ON th.THEM_ID = pt.PT_THEM_ID
      LEFT JOIN thematique_organisme th_org ON th.THEM_ID = th_org.TO_THEM_ID
      LEFT JOIN profil pr ON pt.PT_PROF_ID = pr.PROF_ID
      LEFT JOIN organisme org ON th_org.TO_ORG_ID = org.ORG_ID
      LEFT JOIN thematique th1 ON th.THEM_ID_PERE = th1.THEM_ID
      LEFT JOIN thematique th2 ON th1.THEM_ID_PERE = th2.THEM_ID
      LEFT JOIN thematique th3 ON th2.THEM_ID_PERE = th3.THEM_ID
      LEFT JOIN thematique th4 ON th3.THEM_ID_PERE = th4.THEM_ID
      WHERE th.THEM_AFFICHE = 1; -- AND th.THEM_LEVEL != 0;
    RESULT -> ListBuilder
AttributeManager_2
    ATTR_TABLE:
      SET_TO THEM_ID1 = @Value(_list{0}.THEM_ID1)
      SET_TO THEM_NOM1 = @Value(_list{0}.THEM_NOM1)
      SET_TO THEM_ID2 = @Value(_list{0}.THEM_ID2)
      SET_TO THEM_NOM2 = @Value(_list{0}.THEM_NOM2)
      SET_TO THEM_ID3 = @Value(_list{0}.THEM_ID3)
      SET_TO THEM_NOM3 = @Value(_list{0}.THEM_NOM3)
      SET_TO THEM_ID4 = @Value(_list{0}.THEM_ID4)
      SET_TO THEM_NOM4 = @Value(_list{0}.THEM_NOM4)
      RENAME_SET_VALUE _concatenated > THEM_PROFIL
      SET_TO ORG_DATECREA = @DateTimeFormat(@Value(_list{0}.ORG_DATECREA), %d/%m/%Y)
      SET_TO ORG_DATEMAJ = @DateTimeFormat(@Value(_list{0}.ORG_DATEMAJ), %d/%m/%Y)
      SET_TO TASCOLLSIRET = $(NUMERO_SIRET)
      SET_TO TASCOLLNOM = $(NOM_PRODUCTEUR)
      SET_TO TASCOLLMODIFICATION = @DateTimeFormat(@DateTimeNow(),%Y-%m-%dT%H:%M:%SZ)
    -> FeatureWriter [Output]
FeatureWriter
    CSV2_COORDINATE_SYSTEM_GRANULARITY = FEATURE_TYPE
    CSV2_DELIMITER = ;
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(REPERTOIRE_LOCAL_DEPOT)
    DATASET_ATTR = _dataset
    FEATURE_TYPE_LIST_ATTR = _feature_types
    FORMAT = CSV2
    TOTAL_FEATURES_WRITTEN_ATTR = _total_features_written
    SUMMARY -> CKANExistsResource
Creator
    GEOMTYPE = Geometry Object
    NUM = 1
    CREATED -> CKANConnector
CKANConnector
    OPERATION_TYPE = Update Resource
    PARAMETER_SETUP = _FME_SOURCE_TYPE]File]_FME_SOURCE_FILE]$(FME_MF_DIR)theme_annuaire_social_31-05-2023.csv]_FME_DATA_TO_UPLOAD]<Unused>]_FME_UPLOAD_ATTR_FILENAME]<Unused>]_URL]<Unused>]_PACKAGE_ID]theme-test]_ID]dc63e6c9-cd14-4620-9d81-e77c68583848]_NAME]theme_annuaire_social.csv]_DESCRIPTION]Données sur les collèges brétiliens au format CSV.]_FORMAT]CSV]_MIMETYPE]]_JSON_ATTRIBUTE]]FME_CONTROLLER_QUERY_FILE]ckan_deps/Update Resource.fme]FME_CONTROLLER_CHOICE]Update Resource
    __ckan_connection = CKAN_PROD

Bookmark: Groupe de PROF_NOM par thematique + concaténation de la liste généré
ListBuilder
    GROUP_BY = THEM_ID THEM_LEVEL THEM_NOM
    LIST_ATTRS_TO_INCLUDE = PROF_NOM THEM_ID1 THEM_NOM1 ORG_DATECREA ORG_DATEMAJ THEM_ID2 THEM_ID3 THEM_ID4 THEM_NOM2 THEM_NOM3 THEM_NOM4
    LIST_NAME = _list
    -> ListConcatenator
ListConcatenator
    DROP_EMPTY_PARTS = Yes
    LIST_ATTR = _list{}.PROF_NOM
    SEP = " / "
    VAL_ATTR = _concatenated
    -> AttributeManager_2

Bookmark: DIfusion du fichier crée sur le portail Ille-et-Vilaine via connecteur CKAN
CKANExistsResource
    CKAN_CONNECTION = $(CKAN_CONNECTION)
    DATASET = $(DATASET)
    FILENAME = $(PREFIXE_NOM_FICHIER_SORTIE).csv
    -> Tester
Tester
    BOOL_OP = OR
    COMPOSITE_TEST = 1
    TEST_CLAUSE = CASE_INSENSITIVE_TEST @Value(isExist) = true
    TEST_MODE = CASE_INSENSITIVE_TEST
    PASSED -> CKAN
    FAILED -> CKAN_2
Note: Upload du fichier sur CKAN
CKAN: CKANConnector
    OPERATION_TYPE = Update Resource
    PARAMETER_SETUP = _FME_SOURCE_TYPE]File]_FME_SOURCE_FILE]$(REPERTOIRE_LOCAL_DEPOT)\$(PREFIXE_NOM_FICHIER_SORTIE)_@DateTimeFormat(@DateTimeNow(),%d-%m-%Y).csv]_FME_DATA_TO_UPLOAD]<Unused>]_FME_UPLOAD_ATTR_FILENAME]<Unused>]_URL]<Unused>]_PACKAGE_ID]$(DATASET)]_ID]@Value(id)]_NAME]$(PREFIXE_NOM_FICHIER_SORTIE).csv]_DESCRIPTION]Données sur les thèmes de l'annuaire social préparées au format CSV.]_FORMAT]CSV]_MIMETYPE]@Value(mimeType)]_JSON_ATTRIBUTE]]FME_CONTROLLER_QUERY_FILE]ckan_deps/Update Resource.fme]FME_CONTROLLER_CHOICE]Update Resource
    __ckan_connection = $(CKAN_CONNECTION)
Note: Création du fichier sur CKAN
CKAN_2: CKANConnector
    OPERATION_TYPE = Create Resource
    PARAMETER_SETUP = _FME_SOURCE_TYPE]File]_FME_SOURCE_FILE]$(REPERTOIRE_LOCAL_DEPOT)\$(PREFIXE_NOM_FICHIER_SORTIE)_@DateTimeFormat(@DateTimeNow(),%d-%m-%Y).csv]_FME_DATA_TO_UPLOAD]<Unused>]_FME_UPLOAD_ATTR_FILENAME]<Unused>]_URL]<Unused>]_PACKAGE_ID]$(DATASET)]_NAME]$(PREFIXE_NOM_FICHIER_SORTIE).csv]_DESCRIPTION]Données sur les thèmes de l'annuaire social préparées au format CSV.]_FORMAT]CSV]_MIMETYPE]]_JSON_ATTRIBUTE]]FME_CONTROLLER_QUERY_FILE]ckan_deps/Create Resource.fme]FME_CONTROLLER_CHOICE]Create Resource
    __ckan_connection = $(CKAN_CONNECTION)
