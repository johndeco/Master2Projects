FME workspace annuaire_thematique.fmw

Parameters:
- ANNUAIRE_MYSQL_CONNECTION =
- CKAN_CONNECTION =
- CKAN_CONNECTION_SAFE.CKAN.CKANDATASTORE =
- DATASET =
- NOM_PRODUCTEUR =
- NUMERO_SIRET =
- PREFIXE_NOM_FICHIER_SORTIE =
- REPERTOIRE_LOCAL_DEPOT =

Writers:
- SAFE.CKAN.CKANDATASTORE_1: SAFE.CKAN.CKANDATASTORE

Note: annuaire_thematique / @auteur: John Marc Dechaud / @description: Traitement FME permettant de générer les données des thèmes de l'annuaire social. / @Date: 25/05/2023 / @version: 1.1 / @status: Production / @param REPERTOIRE_LOCAL_DEPOT --> Repertoire local de dépot / @param PREFIXE_NOM_FICHIER_SORTIE --> Prefix ou nom du fichier de sortie / @param ANNUAIRE_MYSQL_CONNECTION --> Nom de la connexion mysql à utiliser / @param NOM_PRODUCTUER --> Nom du producteur de la donnée dans notre cas c'est le département D'Ille-et-vilaine / @param NUMERO_SIRET --> Numero de siret du département / @param CKAN_CONNECTION --> Nom de la connection au serveur CKAN / @param DATASET -->Nom du jeu de données pour éeposer le fichier / @changelog / 25/05/2023 v1.0 JMD --> Création du traitement
SQLCreator_2
    DATASET = $(ANNUAIRE_MYSQL_CONNECTION)
    EXPOSED_ATTRIBUTE_LIST = THEM_ID THEM_NOM THEM_LEVEL THEM_ID_PERE PROF_NOM ORG_DATECREA ORG_DATEMAJ
    FORMAT = MYSQL
    MYSQL_NAMED_CONNECTION = $(ANNUAIRE_MYSQL_CONNECTION)
    SQL_STATEMENT:
      SELECT th.THEM_ID, th.THEM_NOM, th.THEM_LEVEL, th.THEM_ID_PERE, pr.PROF_NOM, org.ORG_DATECREA, org.ORG_DATEMAJ FROM annuaire.thematique th
      LEFT JOIN profil_thematique pt ON th.THEM_ID = pt.PT_THEM_ID
      LEFT JOIN thematique_organisme th_org ON th.THEM_ID = th_org.TO_THEM_ID
      LEFT JOIN profil pr ON pt.PT_PROF_ID = pr.PROF_ID
      LEFT JOIN organisme org ON th_org.TO_ORG_ID = org.ORG_ID
      WHERE th.THEM_AFFICHE = 1 AND th.THEM_LEVEL != 0;
    RESULT -> SQLExecutor [INITIATOR]
SQLExecutor
    ATTR_IGNORE_NULLS = Yes
    COMBINE_ATTRS = Keep Initiator Attributes if Conflict
    COMBINE_GEOM = Initiator Geometry Only
    DATASET = $(ANNUAIRE_MYSQL_CONNECTION)
    EXPOSED_ATTRIBUTE_LIST = THEM_ID1 THEM_NOM1
    FORMAT = MYSQL
    MYSQL_NAMED_CONNECTION = $(ANNUAIRE_MYSQL_CONNECTION)
    SQL_STATEMENT = SELECT THEM_ID AS THEM_ID1, THEM_NOM AS THEM_NOM1 FROM annuaire.thematique WHERE THEM_AFFICHE = 1 AND THEM_ID = @Value(THEM_ID_PERE);
    RESULT -> AttributeManager
    INITIATOR -> AttributeManager
SQLCreator_3
    DATASET = $(ANNUAIRE_MYSQL_CONNECTION)
    EXPOSED_ATTRIBUTE_LIST = THEM_ID THEM_NOM THEM_LEVEL THEM_ID1 THEM_NOM1 PROF_NOM
    FORMAT = MYSQL
    MYSQL_NAMED_CONNECTION = $(ANNUAIRE_MYSQL_CONNECTION)
    SQL_STATEMENT:
      SELECT th.THEM_ID, th.THEM_NOM, th.THEM_LEVEL FROM annuaire.thematique th
      WHERE THEM_AFFICHE = 1 AND THEM_LEVEL = 0;
    RESULT -> AttributeManager
AttributeManager
    ATTR_TABLE:
      SET_TO TASCOLLSIRET
      SET_TO TASCOLLNOM
      SET_TO TASCOLLMODIFICATION
      REMOVE THEM_ID_PERE
      REMOVE _matched_records
    -> ListBuilder
ListBuilder
    GROUP_BY = THEM_ID THEM_LEVEL THEM_NOM
    LIST_ATTRS_TO_INCLUDE = PROF_NOM THEM_ID1 THEM_NOM1 ORG_DATECREA ORG_DATEMAJ
    LIST_NAME = _list
    -> ListConcatenator
ListConcatenator
    DROP_EMPTY_PARTS = Yes
    LIST_ATTR = _list{}.PROF_NOM
    SEP = " / "
    VAL_ATTR = _concatenated
    -> AttributeManager_2
AttributeManager_2
    ATTR_TABLE:
      SET_TO THEM_ID1 = @Value(_list{0}.THEM_ID1)
      SET_TO THEM_NOM1 = @Value(_list{0}.THEM_NOM1)
      RENAME_SET_VALUE _concatenated > THEM_PROFIL
      SET_TO ORG_DATECREA = @DateTimeFormat(@Value(_list{0}.ORG_DATECREA), %d/%m/%Y)
      SET_TO ORG_DATEMAJ = @DateTimeFormat(@Value(_list{0}.ORG_DATEMAJ), %d/%m/%Y)
      SET_TO TASCOLLSIRET = $(NUMERO_SIRET)
      SET_TO TASCOLLNOM = $(NOM_PRODUCTEUR)
      SET_TO TASCOLLMODIFICATION = @DateTimeFormat(@DateTimeNow(),%Y-%m-%dT%H:%M:%SZ)
    -> FeatureWriter [Output]
FeatureWriter
    CSV2_COORDINATE_SYSTEM_GRANULARITY = FEATURE_TYPE
    CSV2_DELIMITER = ;
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(REPERTOIRE_LOCAL_DEPOT)
    DATASET_ATTR = _dataset
    FEATURE_TYPE_LIST_ATTR = _feature_types
    FORMAT = CSV2
    TOTAL_FEATURES_WRITTEN_ATTR = _total_features_written
    SUMMARY -> CKANExistsResource

Bookmark: DIfusion du fichier crée sur le portail Ille-et-Vilaine via connecteur CKAN
CKANExistsResource
    CKAN_CONNECTION = $(CKAN_CONNECTION)
    DATASET = $(DATASET)
    FILENAME = $(PREFIXE_NOM_FICHIER_SORTIE).csv
    -> Tester
Tester
    BOOL_OP = OR
    COMPOSITE_TEST = 1
    TEST_CLAUSE = CASE_INSENSITIVE_TEST @Value(isExist) = true
    TEST_MODE = CASE_INSENSITIVE_TEST
    PASSED -> CKAN
    FAILED -> CKAN_2
Note: Upload du fichier sur CKAN
CKAN: CKANConnector
    OPERATION_TYPE = Update Resource
    PARAMETER_SETUP = _FME_SOURCE_TYPE]File]_FME_SOURCE_FILE]$(REPERTOIRE_LOCAL_DEPOT)\$(PREFIXE_NOM_FICHIER_SORTIE)_@DateTimeFormat(@DateTimeNow(),%d-%m-%Y).csv]_FME_DATA_TO_UPLOAD]<Unused>]_FME_UPLOAD_ATTR_FILENAME]<Unused>]_URL]<Unused>]_PACKAGE_ID]$(DATASET)]_ID]@Value(id)]_NAME]$(PREFIXE_NOM_FICHIER_SORTIE).csv]_DESCRIPTION]Données sur les thèmes de l'annuaire social préparées au format CSV.]_FORMAT]CSV]_MIMETYPE]@Value(mimeType)]_JSON_ATTRIBUTE]]FME_CONTROLLER_QUERY_FILE]ckan_deps/Update Resource.fme]FME_CONTROLLER_CHOICE]Update Resource
    __ckan_connection = $(CKAN_CONNECTION)
Note: Création du fichier sur CKAN
CKAN_2: CKANConnector
    OPERATION_TYPE = Create Resource
    PARAMETER_SETUP = _FME_SOURCE_TYPE]File]_FME_SOURCE_FILE]$(REPERTOIRE_LOCAL_DEPOT)\$(PREFIXE_NOM_FICHIER_SORTIE)_@DateTimeFormat(@DateTimeNow(),%d-%m-%Y).csv]_FME_DATA_TO_UPLOAD]<Unused>]_FME_UPLOAD_ATTR_FILENAME]<Unused>]_URL]<Unused>]_PACKAGE_ID]$(DATASET)]_NAME]$(PREFIXE_NOM_FICHIER_SORTIE).csv]_DESCRIPTION]Données sur les thèmes de l'annuaire social préparées au format CSV.]_FORMAT]CSV]_MIMETYPE]]_JSON_ATTRIBUTE]]FME_CONTROLLER_QUERY_FILE]ckan_deps/Create Resource.fme]FME_CONTROLLER_CHOICE]Create Resource
    __ckan_connection = $(CKAN_CONNECTION)
